;;; Read-only export from the active APP-owned working copy. No DWG writes.
(vl-load-com)

(defun dwgp:fail (message)
  (setq dwgp:failure message)
  (/ 1 0))

(defun dwgp:join (xs / result)
  (setq result "")
  (foreach x xs (setq result (strcat result (if (= result "") "" ",") x)))
  result)

(defun dwgp:control (n)
  (strcat "\\u00" (substr "0123456789abcdef" (1+ (fix (/ n 16))) 1)
                  (substr "0123456789abcdef" (1+ (rem n 16)) 1)))

(defun dwgp:string (s / out n)
  (setq out "\"")
  (foreach n (vl-string->list s)
    (setq out (strcat out
      (cond ((= n 34) "\\\"") ((= n 92) "\\\\")
            ((= n 10) "\\n") ((= n 13) "\\r") ((= n 9) "\\t")
            ((< n 32) (dwgp:control n)) (T (chr n))))))
  (strcat out "\""))

(defun dwgp:number (v / s)
  (setq s (rtos v 2 16))
  (if (= (substr s 1 1) ".") (setq s (strcat "0" s)))
  (if (= (substr s 1 2) "-.") (setq s (strcat "-0" (substr s 2))))
  (if (= (substr s (strlen s)) ".") (setq s (strcat s "0")))
  s)

(defun dwgp:json (v)
  (cond ((eq v :vlax-true) "true")
        ((eq v :vlax-false) "false")
        ((eq v T) "true")
        ((= (type v) 'VARIANT) (dwgp:json (vlax-variant-value v)))
        ((= (type v) 'SAFEARRAY) (dwgp:json (vlax-safearray->list v)))
        ((= (type v) 'STR) (dwgp:string v))
        ((= (type v) 'INT) (itoa v))
        ((= (type v) 'REAL) (dwgp:number v))
        ((null v) "null")
        ((listp v) (strcat "[" (dwgp:join (mapcar 'dwgp:json v)) "]"))
        (T (dwgp:fail (strcat "unsupported bulk value: " (vl-princ-to-string v))))))

(defun dwgp:object (pairs)
  (strcat "{" (dwgp:join (mapcar '(lambda (p) (strcat (dwgp:string (car p)) ":" (cdr p))) pairs)) "}"))

(defun dwgp:prop (o p / v)
  (setq v (vl-catch-all-apply 'vlax-get-property (list o p)))
  (if (vl-catch-all-error-p v)
    "{\"error\":\"property read failed\"}" (dwgp:json v)))

(defun dwgp:entity (o / name props pairs p attrs coords count bulges i blockname)
  (setq dwgp:count (1+ dwgp:count))
  (if (> dwgp:count 20000) (dwgp:fail "bulk entity budget exceeded"))
  (setq name (vla-get-ObjectName o))
  (setq pairs (list (cons "ObjectName" (dwgp:string name))))
  (setq props nil)
  (cond
    ((wcmatch (strcase name) "*BLOCKREFERENCE*")
      (setq props '("Handle" "Name" "InsertionPoint" "Rotation" "XScaleFactor" "YScaleFactor" "HasAttributes"))
      (setq blockname (vla-get-Name o))
      (if (not (member blockname dwgp:seen))
        (progn (setq dwgp:seen (cons blockname dwgp:seen))
               (setq dwgp:pending (cons blockname dwgp:pending))))
      (setq pairs (cons (cons "EffectiveName"
        (if (vlax-property-available-p o 'EffectiveName) (dwgp:prop o 'EffectiveName) (dwgp:string blockname))) pairs))
      (if (= (vla-get-HasAttributes o) :vlax-true)
        (progn
          (setq attrs (vlax-invoke o 'GetAttributes))
          (setq pairs (cons (cons "Attributes" (strcat "[" (dwgp:join (mapcar 'dwgp:entity attrs)) "]")) pairs)))))
    ((wcmatch (strcase name) "*TEXT*,*ATTRIBUTE*")
      (setq props '("Handle" "TextString" "InsertionPoint")))
    ((= (strcase name) "ACDBLINE")
      (setq props '("Handle" "StartPoint" "EndPoint")))
    ((= (strcase name) "ACDBPOLYLINE")
      (setq props '("Handle" "Coordinates" "Closed" "Elevation" "Normal"))
      (setq coords (vlax-get o 'Coordinates))
      (setq count (/ (length coords) 2))
      (if (/= (vla-get-Closed o) :vlax-true) (setq count (1- count)))
      (setq i 0 bulges nil)
      (repeat count
        (setq bulges (cons (vla-GetBulge o i) bulges) i (1+ i)))
      (setq pairs (cons (cons "Bulges" (dwgp:json (reverse bulges))) pairs))))
  (foreach p props (setq pairs (cons (cons p (dwgp:prop o p)) pairs)))
  (dwgp:object pairs))

(defun dwgp:overlaps (o bounds / lo hi)
  ;; Bounding boxes are WCS and independent of saved pan/zoom/UCS. This is a
  ;; conservative prefilter; exact line matching and budgets remain in Python.
  (vla-GetBoundingBox o 'lo 'hi)
  (setq lo (vlax-safearray->list lo) hi (vlax-safearray->list hi))
  (and (<= (car lo) (nth 2 bounds)) (>= (car hi) (nth 0 bounds))
       (<= (cadr lo) (nth 3 bounds)) (>= (cadr hi) (nth 1 bounds))))

(defun dwgp:collect (doc types bounds / roots name block items defs ft fd owner)
  (setq dwgp:count 0 dwgp:pending nil dwgp:seen nil dwgp:failure nil roots nil defs nil)
  ;; Both ssget crossing and GstarCAD ActiveX crossing depend on the viewport.
  ;; Select by type globally, then bound the exported entities inside CAD.
  (setq dwgp:ss (vla-Add (vla-get-SelectionSets doc) (strcat "DWGP_BULK_" dwgp:token)))
  (setq ft (vlax-make-safearray vlax-vbInteger '(0 . 0)))
  (setq fd (vlax-make-safearray vlax-vbVariant '(0 . 0)))
  (vlax-safearray-put-element ft 0 0)
  (vlax-safearray-put-element fd 0 types)
  (vla-Select dwgp:ss 5 (vlax-make-variant) (vlax-make-variant) ft fd)
  (if (> (vla-get-Count dwgp:ss) 20000) (dwgp:fail "bulk root scan budget exceeded"))
  (setq owner (vla-get-ObjectID (vla-get-Block (vla-get-ActiveLayout doc))))
  (vlax-for o dwgp:ss
    (if (and (= (vla-get-OwnerID o) owner)
             (or (null bounds) (dwgp:overlaps o bounds)))
      (setq roots (cons (dwgp:entity o) roots))))
  (while dwgp:pending
    (if (> (length dwgp:seen) 2048) (dwgp:fail "bulk block budget exceeded"))
    (setq name (car dwgp:pending) dwgp:pending (cdr dwgp:pending) items nil)
    (setq block (vla-Item (vla-get-Blocks doc) name))
    (vlax-for o block (setq items (cons (dwgp:entity o) items)))
    (setq defs (cons (cons name (strcat "[" (dwgp:join (reverse items)) "]")) defs)))
  (list (strcat "[" (dwgp:join (reverse roots)) "]") (dwgp:object defs)))

(defun dwgp:run (out token types bounds / doc result cleanup pairs stream temporary)
  (setq doc (vla-get-ActiveDocument (vlax-get-acad-object)))
  (setq dwgp:token token dwgp:ss nil)
  (setq result (vl-catch-all-apply 'dwgp:collect (list doc types bounds)))
  (if dwgp:ss
    (progn
      (setq cleanup (vl-catch-all-apply 'vla-Delete (list dwgp:ss)))
      (if (and (vl-catch-all-error-p cleanup) (not (vl-catch-all-error-p result)))
        (setq result cleanup dwgp:failure "could not delete bulk selection set"))))
  (setq dwgp:ss nil)
  (setq pairs (list (cons "version" "1") (cons "token" (dwgp:string token))
    (cons "document" (dwgp:string (vla-get-FullName doc))) (cons "complete" "true")))
  (setq pairs (append pairs (if (vl-catch-all-error-p result)
    (list (cons "error" (dwgp:string (if dwgp:failure dwgp:failure (vl-catch-all-error-message result)))))
    (list (cons "entities" (car result)) (cons "blocks" (cadr result))))))
  (setq temporary (strcat out ".part"))
  (setq stream (open temporary "w"))
  (if (null stream) (dwgp:fail "cannot open bulk response"))
  (write-line (dwgp:object pairs) stream)
  (close stream)
  (vl-file-rename temporary out)
  (princ))
